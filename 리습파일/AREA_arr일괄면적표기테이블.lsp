;忙式式式式式式式式式式式式式式式式式式式式式忖
;弛              Ⅵ 橾婪 賊瞳 ル晦 Ⅵ
;弛        Program By.   Jeong Kil Bok
;弛        E-mail:   810storm@Daum.net
;弛        Sep  26, 2008  Rev. Oct  07, 2008
;戌式式式式式式式式式式式式式式式式式式式式式戎

(defun c:arr ( / doc space ss n sum obj sp ep cplst area sum cdn mp v sa xp yp pt
				 chlst txtobj  objname table arlst cnt enlst ptlst olden newen xlst sum)
	(vl-load-com)
	(setq doc (vla-get-activedocument(vlax-get-acad-object)))
	(setq space (if (= (getvar "cvport") 1)(vla-get-paperspace doc)(vla-get-modelspace doc)))
	(prompt "\n>> 橾婪 賊瞳 掘ж晦")
	(if (not (setq ss (ssget '((0 . "line,lwpolyline,circle,ellipse,region"))))) (exit))
	(setq $sn (memory "模熱濠葬 殮溘" 2 $sn))  ;模熱濠葬 晦獄高 滲唳衛 2蒂 滲唳
	(setq $tsz (memory "僥濠觼晦 殮溘" 10 $tsz))  ;僥濠觼晦 晦獄高 滲唳衛 10擊 滲唳
	(setq n 0)
	(repeat (sslength ss)
		(setq obj (vlax-ename->vla-object (setq en (ssname ss n))))
		(setq objname (vla-get-objectname obj))
		(if (equal objname "AcDbLine")
			(progn
				(setq pt (list (vlax-get obj 'startpoint) (vlax-get obj 'endpoint)))
				(setq ptlst (append ptlst (list pt)))
				(setq enlst (cons en enlst))
			)
		)
		(setq n (1+ n))
	)
	(if enlst
		(progn
			(foreach x enlst (setq ss (ssdel x ss)))
			(setq olden (getenlst nil))
			(foreach x (connectlst ptlst)
				(if (equal (distance (car x) (last x)) 0 0.1)
					(progn
						(setq lst (apply 'append (mapcar '(lambda (z) (list (car z) (cadr z))) x)))				
						(vla-addlightweightpolyline space (vlax-make-variant (vlax-safearray-fill 
						(vlax-make-safearray vlax-vbdouble (cons 0 (- (length lst) 1))) lst)))
					)
				)
			)
			(setq newen (getenlst nil))
			(setq chlst (makelst olden newen))
			(foreach x chlst (setq ss (ssadd x ss)))
		)
	)
	(setq n 0 sum 0 val (/ 2.0 3.0))
	(repeat (sslength ss)
		(setq obj (vlax-ename->vla-object (ssname ss n)))
		(setq objname (vla-get-objectname obj))
		(if (equal objname "AcDbPolyline")
			(progn
				(setq sp (vlax-curve-getstartpoint obj) ep (vlax-curve-getendpoint obj) cplst nil)		
				(if (equal (distance sp ep) 0 0.1) (vla-put-closed obj :vlax-true))				
				(if (vlax-curve-isclosed obj)
					(progn
						(setq area (rtos (* (vla-get-area obj) 0.000001) 2 $sn))
						(setq cdn (append (cdr (divlst (vlax-get obj 'coordinates) 2)) (list sp)))
						(foreach x cdn
							(setq mp (polar sp (angle sp x) (/ (distance sp x) 2)))
							(setq v (/ (- (* (car sp) (cadr x)) (* (cadr sp) (car x))) 2))
							(setq cplst (append cplst (list (list (car mp) (cadr mp) v))) sp x)		
						)
						(setq sa (apply '+ (mapcar '(lambda (x) (caddr x)) cplst)))
						(setq xp (apply '+ (mapcar '(lambda (x) (* (car x) (/ (* (caddr x) val) sa))) cplst)))
						(setq yp (apply '+ (mapcar '(lambda (x) (* (cadr x) (/ (* (caddr x) val) sa))) cplst)))
						(setq pt (list xp yp))
						(setq arlst (append arlst (list (list pt area))))
					)
				)
			)
			(progn
				(setq area (rtos (* (vla-get-area obj) 0.000001) 2 $sn))
				(if (equal objname "AcDbRegion")
					(setq pt (append (vlax-get obj 'centroid) (list 0.0)))
					(setq pt (vlax-get obj 'center))					
				)
				(setq arlst (append arlst (list (list pt area))))
			)
		)		
		(setq n (1+ n))
	)
	(if chlst (foreach x chlst (vla-delete (vlax-ename->vla-object x))))
	(setq arlst (vl-sort (vl-sort arlst '(lambda (a b) (< (car (car a)) (car (car b))))) '(lambda (a b) (> (cadr (car a)) (cadr (car b))))))
	(setq n 1)
	(foreach x arlst
		(setq pt (vlax-3d-point (car x)))
		;(setq txtobj (vla-addtext space (strcat (rtos n) " : " (cadr x)) pt $tsz)) ;no number (strcat (rtos n) " : " (cadr x))  ╮  (cadr x); 錳獄
		(setq txtobj (vla-addtext space (strcat (rtos n 2 0) ") 賊瞳(M2) : " (cadr x)) pt $tsz)) ;no number (strcat (rtos n) " : " (cadr x))  ╮  (cadr x)
		(vla-put-alignment txtobj 4)
		(vla-put-textalignmentpoint txtobj pt)
		(vla-update txtobj)
		(setq n (1+ n))
	)
	(if (not (equal (setq sum (rtos (apply '+ (mapcar '(lambda (x) (atof (cadr x))) arlst)) 2 $sn)) "0"))
		(progn	
			(setq cnt (length arlst) n 2)
			(if (setq pt (getpoint "\n>> 纔檜綰 濛撩 ん檣お 雖薑:"))
				(progn
					(setq table (vla-addtable space (vlax-3d-point pt) (+ cnt 3) 2 (* $tsz 2) (* $tsz 10)))
					(vla-settext table 0 0 "Area Table")
					(vla-settext table 1 0 "No.")
					(vla-settext table 1 1 "賊瞳(M2)")
					(vla-settext table (+ cnt 2) 0 "Total")
					(vla-settext table (+ cnt 2) 1 sum)
					(foreach x arlst
						(vla-settext table n 0 (itoa (- n 1)))
						(vla-settext table n 1 (cadr x))
						(setq n (1+ n))
					)
					(setq n 0)
					(repeat (+ cnt 3)
						(vla-setcelltextheight table n 0 $tsz)
						(vla-setcellalignment table n 0 5)
						(vla-setcelltextheight table n 1 $tsz)
						(vla-setcellalignment table n 1 5)
						(setq n (1+ n))
					)
					(vla-setcolumnwidth table 0 (* $tsz 6))
				)
			)
		)
	)
	(princ)
)

(defun memory (msg bval mval / sval)
	(if (equal mval nil) (setq mval bval))
	(initget 4)
	(setq sval (getint (strcat "\n>> " msg " <" (rtos mval 2 0) ">:")))
	(if sval (setq mval sval) mval)
)

(defun makelst (old new / )
	(foreach x old
		(if (member x new) (setq new  (vl-remove x new)))
	)
	new
)

(defun getenlst (sets / enlst i)
	(if (not sets) (setq sets (ssget "x")))
	(setq i 0)
	(repeat (sslength sets)
		(setq enlst (cons (ssname sets i) enlst))
		(setq i (1+ i))
	)
	enlst
)

(defun divlst (lst num / e blst lst newlst)
	(while (setq e (car lst))
		(repeat num
			(if e (setq blst (cons e blst)))
			(setq lst (cdr lst) e (car lst))			
		)
		(setq newlst (append newlst (list (reverse blst))) blst nil)
	)
	newlst
)

(defun connectlst (lst / n re en tn)
	(setq n 0)
	(while (> (length lst) n)
		(setq en (nth n lst) tn nil)		
		(foreach x (cdr lst)
			(if (and (equal (distance (last en) (car x)) 0 0.1) (not (equal en x)))
				(progn
					(setq lst (subst (append en (cdr x)) en lst))
					(setq lst (vl-remove x lst) tn t)
				)
			)
			(if (and (equal (distance (last en) (last x)) 0 0.1) (not (equal en x)))
				(progn
					(setq lst (subst (append en (cdr (reverse x))) en lst))
					(setq lst (vl-remove x lst) tn t)
				)
			)
		)
		(if tn (setq n 0) (setq n (1+ n)))
	)
	lst
)

(defun *error* (msg)
	(if (/= msg "function cancelled")
		(if (= msg "quit / exit abort")
			(princ)
			(princ (strcat "\nerror: " msg))
		)
		(princ)
	)
	(princ)
)
